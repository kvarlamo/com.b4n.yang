/*
 * Copyright (c) 2016 Brain4Net.  All rights reserved.
 */

module b4n-orc {
    yang-version 1;
    namespace "urn:b4n:orc";
    prefix orc;

    import ietf-inet-types {
      prefix inet;
    }
    import ietf-yang-types {
      prefix yang;
    }
    import ietf-interfaces {
      prefix if;
    }
    import ex-ethernet-bonding { prefix bond;}
    import ex-vlan { prefix vlan;}

    import b4n-orc-L2Services {prefix "L2";}
    organization "Brain4Net";
    contact "Kirill Varlamov <k.varlamov@brain4net.com>";
    description "This YANG module defines a top level for B4N orchestrator models.";

    revision "2016-03-09" {
        description
                "Brain4Net";
    }
}
