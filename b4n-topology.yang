module topology {
    namespace "http://brain4net.com/topology";
    prefix "topo";
    import ietf-interfaces { prefix if; revision-date "2014-05-08"; }
    import ietf-yang-types {
        prefix yang;
      }
    organization "Brain4Net";
    contact "k.varlamov@brain4net.com";
    
    description
        " ";
    
    revision 2007-06-09 {
        description "Initial revision.";
    }
    
    container topology {
        description "";
    
        container switches {
            description "";
            
    
            list switch {
                description "";
                key sid;
                leaf leaf9 {
                    description "";
                    type string;
                }
                leaf sid {
                    description "";
                    type uint8;
                }
    
                leaf active {
                    description "";
                    type enumeration {
                    	enum yes;
                    	enum no;
                    }
                }
                leaf connected {
                    description "";
                    type enumeration {
                    	enum yes;
                    	enum no;
                    }
                }
                leaf  mac {
                    description "";
                    type string;
                }
                leaf ip {
                    description "";
                    type string;
                }
                leaf port {
                    description "";
                    type string;
                }
                leaf since {
                    description "";
                    type string;
                }
                leaf location {
                    description "";
                    type string;
                }
                }         
                
            }

        config false;
        description
          "Data nodes for the operational state of interfaces.";

        list interface {
          key id;





          description
            "The list of interfaces on the device.

             System-controlled interfaces created by the system are
             always present in this list, whether they are configured or
             not.";

          leaf id {
            type string;
            description
              "The name of the interface.

               A server implementation MAY map this leaf to the ifName
               MIB object.  Such an implementation needs to use some
               mechanism to handle the differences in size and characters
               allowed between this leaf and ifName.  The definition of
               such a mechanism is outside the scope of this document.";
            reference
              "RFC 2863: The Interfaces Group MIB - ifName";
          }

          leaf type {
            type identityref {
              base interface-type;
            }
            mandatory true;
            description
              "The type of the interface.";
            reference
              "RFC 2863: The Interfaces Group MIB - ifType";
          }

          leaf admin-status {
            if-feature if-mib;
            type enumeration {
              enum up {
                value 1;
                description
                  "Ready to pass packets.";
              }
              enum down {
                value 2;
                description
                  "Not ready to pass packets and not in some test mode.";
              }



              enum testing {
                value 3;
                description
                  "In some test mode.";
              }
            }
            mandatory true;
            description
              "The desired state of the interface.

               This leaf has the same read semantics as ifAdminStatus.";
            reference
              "RFC 2863: The Interfaces Group MIB - ifAdminStatus";
          }

          leaf oper-status {
            type enumeration {
              enum up {
                value 1;
                description
                  "Ready to pass packets.";
              }
              enum down {
                value 2;
                description
                  "The interface does not pass any packets.";
              }
              enum testing {
                value 3;
                description
                  "In some test mode.  No operational packets can
                   be passed.";
              }
              enum unknown {
                value 4;
                description
                  "Status cannot be determined for some reason.";
              }
              enum dormant {
                value 5;
                description
                  "Waiting for some external event.";
              }
              enum not-present {
                value 6;
                description
                  "Some component (typically hardware) is missing.";
              }
              enum lower-layer-down {
                value 7;
                description
                  "Down due to state of lower-layer interface(s).";
              }
            }
            mandatory true;
            description
              "The current operational state of the interface.

               This leaf has the same semantics as ifOperStatus.";
            reference
              "RFC 2863: The Interfaces Group MIB - ifOperStatus";
          }

          leaf last-change {
            type yang:date-and-time;
            description
              "The time the interface entered its current operational
               state.  If the current state was entered prior to the
               last re-initialization of the local network management
               subsystem, then this node is not present.";
            reference
              "RFC 2863: The Interfaces Group MIB - ifLastChange";
          }

          

          

          

          

          leaf speed {
            type yang:gauge64;
            units "bits/second";
            description
                "An estimate of the interface's current bandwidth in bits
                 per second.  For interfaces that do not vary in
                 bandwidth or for those where no accurate estimation can
                 be made, this node should contain the nominal bandwidth.
                 For interfaces that have no concept of bandwidth, this
                 node is not present.";
            reference
              "RFC 2863: The Interfaces Group MIB -
                         ifSpeed, ifHighSpeed";
          }









          container statistics {
            description
              "A collection of interface-related statistics objects.";

            leaf discontinuity-time {
              type yang:date-and-time;
              mandatory true;
              description
                "The time on the most recent occasion at which any one or
                 more of this interface's counters suffered a
                 discontinuity.  If no such discontinuities have occurred
                 since the last re-initialization of the local management
                 subsystem, then this node contains the time the local
                 management subsystem re-initialized itself.";
            }

            leaf in-octets {
              type yang:counter64;
              description
                "The total number of octets received on the interface,
                 including framing characters.

                 Discontinuities in the value of this counter can occur
                 at re-initialization of the management system, and at
                 other times as indicated by the value of
                 'discontinuity-time'.";
              reference
                "RFC 2863: The Interfaces Group MIB - ifHCInOctets";
            }

            leaf in-unicast-pkts {
              type yang:counter64;
              description
                "The number of packets, delivered by this sub-layer to a
                 higher (sub-)layer, that were not addressed to a
                 multicast or broadcast address at this sub-layer.

                 Discontinuities in the value of this counter can occur
                 at re-initialization of the management system, and at
                 other times as indicated by the value of
                 'discontinuity-time'.";
              reference
                "RFC 2863: The Interfaces Group MIB - ifHCInUcastPkts";
            }




            leaf in-broadcast-pkts {
              type yang:counter64;
              description
                "The number of packets, delivered by this sub-layer to a
                 higher (sub-)layer, that were addressed to a broadcast
                 address at this sub-layer.

                 Discontinuities in the value of this counter can occur
                 at re-initialization of the management system, and at
                 other times as indicated by the value of
                 'discontinuity-time'.";
              reference
                "RFC 2863: The Interfaces Group MIB -
                           ifHCInBroadcastPkts";
            }

            leaf in-multicast-pkts {
              type yang:counter64;
              description
                "The number of packets, delivered by this sub-layer to a
                 higher (sub-)layer, that were addressed to a multicast
                 address at this sub-layer.  For a MAC-layer protocol,
                 this includes both Group and Functional addresses.

                 Discontinuities in the value of this counter can occur
                 at re-initialization of the management system, and at
                 other times as indicated by the value of
                 'discontinuity-time'.";
              reference
                "RFC 2863: The Interfaces Group MIB -
                           ifHCInMulticastPkts";
            }

            leaf in-discards {
              type yang:counter32;
              description
                "The number of inbound packets that were chosen to be
                 discarded even though no errors had been detected to
                 prevent their being deliverable to a higher-layer
                 protocol.  One possible reason for discarding such a
                 packet could be to free up buffer space.

                 Discontinuities in the value of this counter can occur
                 at re-initialization of the management system, and at
                 other times as indicated by the value of
                 'discontinuity-time'.";


              reference
                "RFC 2863: The Interfaces Group MIB - ifInDiscards";
            }

            leaf in-errors {
              type yang:counter32;
              description
                "For packet-oriented interfaces, the number of inbound
                 packets that contained errors preventing them from being
                 deliverable to a higher-layer protocol.  For character-
                 oriented or fixed-length interfaces, the number of
                 inbound transmission units that contained errors
                 preventing them from being deliverable to a higher-layer
                 protocol.

                 Discontinuities in the value of this counter can occur
                 at re-initialization of the management system, and at
                 other times as indicated by the value of
                 'discontinuity-time'.";
              reference
                "RFC 2863: The Interfaces Group MIB - ifInErrors";
            }

            leaf in-unknown-protos {
              type yang:counter32;
              description
                "For packet-oriented interfaces, the number of packets
                 received via the interface that were discarded because
                 of an unknown or unsupported protocol.  For
                 character-oriented or fixed-length interfaces that
                 support protocol multiplexing, the number of
                 transmission units received via the interface that were
                 discarded because of an unknown or unsupported protocol.
                 For any interface that does not support protocol
                 multiplexing, this counter is not present.

                 Discontinuities in the value of this counter can occur
                 at re-initialization of the management system, and at
                 other times as indicated by the value of
                 'discontinuity-time'.";
              reference
                "RFC 2863: The Interfaces Group MIB - ifInUnknownProtos";
            }





            leaf out-octets {
              type yang:counter64;
              description
                "The total number of octets transmitted out of the
                 interface, including framing characters.

                 Discontinuities in the value of this counter can occur
                 at re-initialization of the management system, and at
                 other times as indicated by the value of
                 'discontinuity-time'.";
              reference
                "RFC 2863: The Interfaces Group MIB - ifHCOutOctets";
            }

            leaf out-unicast-pkts {
              type yang:counter64;
              description
                "The total number of packets that higher-level protocols
                 requested be transmitted, and that were not addressed
                 to a multicast or broadcast address at this sub-layer,
                 including those that were discarded or not sent.

                 Discontinuities in the value of this counter can occur
                 at re-initialization of the management system, and at
                 other times as indicated by the value of
                 'discontinuity-time'.";
              reference
                "RFC 2863: The Interfaces Group MIB - ifHCOutUcastPkts";
            }

            leaf out-broadcast-pkts {
              type yang:counter64;
              description
                "The total number of packets that higher-level protocols
                 requested be transmitted, and that were addressed to a
                 broadcast address at this sub-layer, including those
                 that were discarded or not sent.

                 Discontinuities in the value of this counter can occur
                 at re-initialization of the management system, and at
                 other times as indicated by the value of
                 'discontinuity-time'.";
              reference
                "RFC 2863: The Interfaces Group MIB -
                           ifHCOutBroadcastPkts";
            }


            leaf out-multicast-pkts {
              type yang:counter64;
              description
                "The total number of packets that higher-level protocols
                 requested be transmitted, and that were addressed to a
                 multicast address at this sub-layer, including those
                 that were discarded or not sent.  For a MAC-layer
                 protocol, this includes both Group and Functional
                 addresses.

                 Discontinuities in the value of this counter can occur
                 at re-initialization of the management system, and at
                 other times as indicated by the value of
                 'discontinuity-time'.";
              reference
                "RFC 2863: The Interfaces Group MIB -
                           ifHCOutMulticastPkts";
            }

            leaf out-discards {
              type yang:counter32;
              description
                "The number of outbound packets that were chosen to be
                 discarded even though no errors had been detected to
                 prevent their being transmitted.  One possible reason
                 for discarding such a packet could be to free up buffer
                 space.

                 Discontinuities in the value of this counter can occur
                 at re-initialization of the management system, and at
                 other times as indicated by the value of
                 'discontinuity-time'.";
              reference
                "RFC 2863: The Interfaces Group MIB - ifOutDiscards";
            }

            leaf out-errors {
              type yang:counter32;
              description
                "For packet-oriented interfaces, the number of outbound
                 packets that could not be transmitted because of errors.
                 For character-oriented or fixed-length interfaces, the
                 number of outbound transmission units that could not be
                 transmitted because of errors.




                 Discontinuities in the value of this counter can occur
                 at re-initialization of the management system, and at
                 other times as indicated by the value of
                 'discontinuity-time'.";
              reference
                "RFC 2863: The Interfaces Group MIB - ifOutErrors";
            }
          }
        }
      }
    	}
    }
}
