module acme-system {
    namespace "http://acme.example.com/system";
    prefix "acme";
    import ietf-interfaces { prefix if; revision-date "2014-05-08"; }
    
    organization "ACME Inc.";
    contact "joe@acme.example.com";
    
    description
        "The module for entities implementing the ACME system.";
    
    revision 2007-06-09 {
        description "Initial revision.";
    }
    
    container system {
        leaf host-name {
            type string;
            description "Hostname for this system";
        }
    
        leaf-list domain-search {
            type string;
            description "List of domain names to search";
        }
    
        container login {
            leaf message {
                type string;
                description
                    "Message given at start of login session";
            }
    
            list user {
                description "";
                key "name";
                leaf name {
                    type string;
                }
    
                leaf full-name {
                    type string;
                }
                
                leaf class {
                    type string;
                }
                leaf leaf6 {
                    description "";
                    type leafref {
                    	path "/if:interfaces/if:interface/if:name";
                    }
                }
            }
        }
    }
}
